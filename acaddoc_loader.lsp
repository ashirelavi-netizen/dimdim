;;; ============================================================
;;;  acaddoc.lsp  -  טוען בלבד (loader)
;;;
;;;  קובץ קטן זה יושב בתיקיית ה-Support של AutoCAD ונטען
;;;  אוטומטית בכל פתיחת שרטוט. כל תפקידו: לטעון את DCOL.lsp
;;;  מתיקיית הפרויקט (המחוברת ל-git).
;;;
;;;  >>> ערוך את הנתיב למטה לתיקיית הפרויקט שלך <<<
;;;  זכור: שני קווים נטויים \\ בכל מקום בנתיב.
;;; ============================================================

(setq *DCOL-PATH* "C:\\Users\\USER\\Documents\\DCOL\\DCOL.lsp")

(if (findfile *DCOL-PATH*)
  (load *DCOL-PATH*)
  (princ (strcat "\n[acaddoc] DCOL.lsp לא נמצא בנתיב: " *DCOL-PATH*))
)
(princ)
